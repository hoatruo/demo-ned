module tailf-ned-GRX {

  namespace "http://tail-f.com/ned/GRX";
  prefix GRX;

  import tailf-common {
    prefix tailf;
  }

  revision 2018-11-12 {
    description
      "1.0.0
       See CHANGES";
  }

  // This is the skeleton for a made-up device that is used
  // in the ned skeleton generator


  list projects {
    key key;
    leaf key {
      tailf:info "Project key must be in upper case";
      type string;
    }

    leaf name {
      mandatory true;
      type string;
    }

    leaf description {
      type string;
    }

    list repos {
      key name;
      leaf name {
        type string;
      }
      leaf slug {
        mandatory true;
        tailf:info "Automatically generated by Bitbucket. 
          Examples: 'føøbar' becomes 'foobar'. 'foo bar' becomes 'foo-bar'. 
          Must be in lower case";
        type string;
      }
    }
  }


  // This is an example of a command, the device - that is controlled
  // by the generic NED has the ability to not only change
  // the configuration, but it also has the ability to execute
  // commands. If we wish to invoke those comands through NCS, we
  // model the command in YANG like below, and we implement
  // the invocation of the command in the NED Java code.

  rpc my-cmd {
    tailf:actionpoint ncsinternal {
      tailf:internal;
    }
    input {
      leaf a {
        type int32;
      }
      leaf b {
        type string;
      }
    }
    output {
      list  item {
        leaf l1 {
          type enumeration {
            enum On;
            enum Off;
          }
        }
        leaf l2 {
          type int32;
        }
      }
    }
  }
}
